module ietf-isis-te-app {
  yang-version 1.1;
  namespace "urn:ietf:params:xml:ns:yang:ietf-isis-te-app";

  prefix isis-te-app;

  import ietf-routing {
    prefix "rt";
  }

  import ietf-isis {
    prefix "isis";
  }

  organization
    "IETF LSR - Link State Routing Working Group";

  contact
     "WG Web:   <http://tools.ietf.org/wg/lsr>
      WG List:  <mailto:lsr@ietf.org>

      Author:   Yingzhen Qu
                <mailto:yqu@futurewei.com>
      Author:   Acee Lindem
                <mailto:acee@cisco.com>
      Author:   Stephane Litkowski
                <mailto:slitkows.ietf@gmail.com>";

  description
    "This YANG module defines the configuration and operational 
    state for IS-IS TE attributes per application feature as defined 
    in RFC xxxx.

     Copyright (c) 2020 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX;
     see the RFC itself for full legal notices.";

  reference "RFC XXXX";

  revision 2020-10-29 {
    description
      "Initial version";
    reference
      "RFC XXXX: A YANG Data Model for IS-IS.";
  }

  augment "/rt:routing/" +
          "rt:control-plane-protocols/rt:control-plane-protocol"+
          "/isis:isis/isis:interfaces/isis:interface" {
    when "/rt:routing/rt:control-plane-protocols/"+
                     "rt:control-plane-protocol/rt:type = 'isis:isis'" {
      description
        "This augment ISIS routing protocol when used";
    }
    description
      "This augments ISIS protocol configuration
       with TE attributes per application.";

    container isis-te-app {
      choice te-app-op-mode {
        mandatory "true";
        leaf legacy {
          type empty;
        }
        leaf transition {
          type empty;
        }
        leaf app-specific{
          type empty;
        }
      }
      description
        "TE attributes per application.";
    }
  }
}
