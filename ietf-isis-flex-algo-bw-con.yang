module ietf-isis-flex-algo-bw-con {
  yang-version 1.1;
  namespace "urn:ietf:params:xml:ns:yang:"
          + "ietf-isis-flex-algo-bw-con";
  prefix isis-flex-algo-bw;

  import ietf-routing {
    prefix rt;
    reference "RFC 8349: A YANG Data Model for Routing
               Management (NMDA Version)";
  }

  import ietf-routing-types {
    prefix "rt-types";
    reference "RFC 8294: Common YANG Data Types for the
               Routing Area";
  }

  import ietf-te-types {
    prefix te-types;
    reference
      "RFC8776: Common YANG Data Types for Traffic Engineering.";
  }

  import ietf-isis {
    prefix isis;
    reference
      "RFC 9130: YANG Data Model for the IS-IS Protocol";
  }

  import ietf-isis-flex-algo {
    prefix isis-flex-algo;
  }

  import ietf-isis-link-attr {
    prefix isis-link-attr;
  }

  import iana-igp-metric-types {
    prefix iana-metric-types;
  }  

  organization
    "IETF LSR - Link State Routing Working Group";
  contact
    "WG Web:   <https://datatracker.ietf.org/wg/lsr/>
     WG List:  <mailto:lsr@ietf.org>


     Author:    Yingzhen Qu
               <mailto:yingzhen.ietf@gmail.com>
     Author:    Acee Lindem
               <mailto:acee.ietf@gmail.com>
    ";

  description
    "The YANG module defines the configuration and operational
     state for IS-IS protocol as defined in
     draft-ietf-lsr-flex-algo-bw-con, IGP Flexible Algorithms:
     Bandwidth, Delay, Metrics and Constraints

     This YANG model conforms to the Network Management
     Datastore Architecture (NMDA) as described in RFC 8342.

     Copyright (c) 2025 IETF Trust and the persons identified as
     authors of the code.  All rights reserved.

     Redistribution and use in source and binary forms, with or
     without modification, is permitted pursuant to, and subject
     to the license terms contained in, the Revised BSD License set
     forth in Section 4.c of the IETF Trust's Legal Provisions
     Relating to IETF Documents
     (https://trustee.ietf.org/license-info).

     This version of this YANG module is part of RFC XXXX;
     see the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";


  reference "RFC XXXX.";

  revision 2025-10-06 {
    description
      "Initial Version";
    reference
      "RFC XXXX";
  }

  /* Identities */

  identity bandwidth-constraint-type {
    description
      "Base identity for bandwidth constraint types.";
  }

  identity min-bw {
    base bandwidth-constraint-type;
    description
      "Minimum bandwidth constraint.";
  }

  identity max-bw {
    base bandwidth-constraint-type;
    description
      "Maximum bandwidth constraint.";
  }

  identity fadrb-flags {
    description
      "Base identity for OSPF Flexible Algorithm Definition
       Reference Bandwidth sub-tlv flags.";
  }

  identity g-bit {
    base fadrb-flags;
    description
      "G bit, when set, interface group mode MUST be used to
       derive total link bandwidth.";
  }

  identity fadbt-flags {
    description
      "Base identity for OSPF Flexible Algorithm Definition
       Reference Bandwidth sub-tlv flags.";
  }

  identity gp-bit {
    base fadbt-flags;
    description
      "G bit, when set, interface group mode MUST be used to
       derive total link bandwidth.";
  }

  /* Groupings */
  grouping bandwidth-constraint {
    description
      "Grouping for bandwidth constraints in Flex-Algo.";
    container bandwidth-constraints {
      list constraint {
        key "constraint-type";
        description
          "List of bandwidth constraints for the Flex-Algo.";
        leaf constraint-type {
          type identityref {
            base bandwidth-constraint-type;
          }
          description
            "Type of bandwidth constraint (e.g., min-bw, max-bw).";
        }
        leaf bandwidth-value {
          type te-types:te-bandwidth;
          description
            "Bandwidth value for the constraint.";
        }
        leaf threshold {
          type uint8 {
            range "1..100";
          }
          units "percent";
          description
            "Threshold percentage for triggering re-optimization.";
        }
      }
      description
        "Bandwidth constraints configuration for flex-algo.";
    }
  }

  grouping generic-metric-sub-tlv {
    container generic-metric-sub-tlvs {
      list generic-metric-sub-tlv {
        leaf metric-type {
          type identityref {
            base iana-metric-types:metric-type;
          }
            description
              "Type of metric to be used during the calculation.";
        }
        leaf value {
          type isis:wide-metric;
          description
            "A 24-bit unsigned integer representing the metric
             value. The valid range is from 0 to 16,777,215
             (0xFFFFFF).";
        }
        description
          "The list of generic metric sub-tlvs.";
      }
      description
        "The generic metric sub-tlv.";
    }
    description
      "The grouping for generic metric sub-tlv.";
  }

  grouping faemb-sub-tlv {
    container faemb-sub-tlv {
      leaf min-bandwidth {
        type rt-types:bandwidth-ieee-float32;
        description
          "A 32-bit field specifying the link bandwidth in IEEE
           floating point format (IEEE754). The units are
           bytes-per-second.";
      }
      description
        "Flex-algo Exclude Minimum Bandwidth sub-tlv (FAEMB).";
    }
    description
      "Grouping for FAEMB sub-tlv.";
  }

  grouping faemd-sub-tlv {
    container faemd-sub-tlv {
      leaf max-link-delay {
        type rt-types:uint24;
        description
          "A 24-bit field specifying the maximum link delay in
           microseconds.";
      }
      description
        "The Flex-algo Exclude Maximum Delay sub-tlv (FAEMD).";
    }
    description
      "Grouping for FAEMD sub-tlv.";
  }

  grouping fadrb-sub-tlv {
    container fadrb-sub-tlv {
      leaf-list fadrb-flags {
        type identityref {
          base fadrb-flags;
        }
        description
          "Flex-algo definition reference bandwidth sub-tlv
           flags list.";
      }
      leaf reference-bandwidth {
        type rt-types:bandwidth-ieee-float32;
        description
          "A 32-bit field specifying the link bandwidth in IEEE
           floating point format (IEEE754). The units are
           bytes-per-second.";
      }
      leaf granularity-bandwidth {
        type rt-types:bandwidth-ieee-float32;
        description
          "A 32-bit field specifying the link bandwidth in IEEE
           floating point format (IEEE754). The units are
           bytes-per-second.";
      }
      description
        "The Flex-algo Reference Bandwidth sub-tlv (FAEMD).";
    }
    description
      "Grouping for FADRB sub-tlv.";
  }

  grouping fadbt-sub-tlv {
    container fadbt-sub-tlv {
      leaf-list fadbt-flags {
        type identityref {
          base fadbt-flags;
        }
        description
          "Flex-algo definition bandwidth thresholds sub-tlv
           flags list.";
      }
      list bandwidth-threshold {
        leaf bandwidth-threshold {
          type rt-types:bandwidth-ieee-float32;
          description
            "Maximum link bandwidth. A 32-bit field specifying
             the link bandwidth in IEEE floating point format
             (IEEE754). The units are bytes-per-second.";
        }

        leaf threshold-metric {
          type rt-types:uint24;
          description
            "Metric value range 1 - 16,777,215 (0xFFFFFF).";
        }
        description
          "List of bandwidth thresholds and metrics.";
      }
      description
        "The Flex-algo Bandwidth Thresholds sub-tlv (FADBT).";
    }
    description
      "Grouping for FADBT sub-tlv."; 
  }  

  /* Configurations */
  augment "/rt:routing/rt:control-plane-protocols/"
        + "rt:control-plane-protocol/isis:isis/"
        + "isis:interfaces/isis:interface" {
    when "/rt:routing/rt:control-plane-protocols/"
       + "rt:control-plane-protocol/rt:type = 'isis:isis'" {
      description
        "This augment ISIS routing protocol when used.";
    }
    description
      "This augments the ISIS protocol interface
       configuration with generic metric configuration.";

    container generic-metrics {
      list generic-metric {
        key "metric-type";
        leaf metric-type {
          type identityref {
            base iana-metric-types:metric-type;
          }
          description
            "Type of metric to be used during the calculation.";
        }
        leaf metric-value {
          type uint32;
          description
            "Metric value, range is from 0 to 0xFFFFFFFF.";
        }
        description
          "Interface generic metric configuration per metric-type.";
      }
      description
        "Interface generic metric configuration.";
    }
  }

  augment "/rt:routing/rt:control-plane-protocols/"
     + "rt:control-plane-protocol/isis:isis/"
     + "isis-flex-algo:isis-flex-algo" {
    when "derived-from(/rt:routing/rt:control-plane-protocols/"
         + "rt:control-plane-protocol/rt:type, 'isis:isis')" {
      description
        "This augments the ISIS routing protocol when used.";
    }
    description
      "This augments ISIS protocol Flexible Algorithm with
       bandwidth constraints.";

    uses bandwidth-constraint;
    choice metric-derivation-method {
      description
        "Choice of automatic metric derivation methods.";
      container reference-bandwidth {
        description
          "Metric is inversely proportional to the link
           bandwidth.";
        leaf reference-bandwidth {
          type rt-types:bandwidth-ieee-float32;
          description
            "A 32-bit field specifying the link bandwidth in IEEE
             floating point format (IEEE754). The units are
             bytes-per-second.";
        }
        leaf granularity-bandwidth {
          type rt-types:bandwidth-ieee-float32;
          description
            "A 32-bit field specifying the link bandwidth in IEEE
             floating point format (IEEE754). The units are
             bytes-per-second.";
        }
      }
      container bandwidth-thresholds {
        description
          "Pre-define non-proportional metric values from the
           varying ranges of link bandwidth.";
        list bandwidth-threshold {
          key bandwidth-threshold;
          leaf bandwidth-threshold {
            type rt-types:bandwidth-ieee-float32;
            description
              "Maximum link bandwidth. A 32-bit field specifying
               the link bandwidth in IEEE floating point format
               (IEEE754). The units are bytes-per-second.";
          }  
          leaf threshold-metric {
            type rt-types:uint24;
            description
              "Metric value range 1 - 16,777,215 (0xFFFFFF).";
          }
          description
            "List of bandwidth thresholds and metrics.";
        }
      }
    }

    leaf exclude-min-bw {
      type rt-types:bandwidth-ieee-float32;
      description
        "A 32-bit field specifying the link bandwidth in IEEE
         floating point format (IEEE754). The units are
         bytes-per-second.";    
    }

    leaf exclude-max-delay {
      type rt-types:uint24;
      description
        "A 24-bit field specifying the maximum link delay in
         microseconds.";    
    }
  }

  /* Database */

  /* TLV 22 */
  augment "/rt:routing/" +
          "rt:control-plane-protocols/rt:control-plane-protocol"+
          "/isis:isis/isis:database/isis:levels/isis:lsp"+
          "/isis:extended-is-neighbor/isis:neighbor"+
          "/isis:instances/isis:instance" {
    when "/rt:routing/rt:control-plane-protocols/"+
         "rt:control-plane-protocol/rt:type = 'isis:isis'" {
      description
        "This augment ISIS routing protocol when used";
    }
    description
      "This augments ISIS protocol LSDB TLV22.";

    uses generic-metric-sub-tlv;
  }

  augment "/rt:routing/" +
          "rt:control-plane-protocols/rt:control-plane-protocol"+
          "/isis:isis/isis:database/isis:levels/isis:lsp"+
          "/isis:extended-is-neighbor/isis:neighbor"+
          "/isis:instances/isis:instance"+
          "/isis-link-attr:asla-sub-tlvs"+
          "/isis-link-attr:asla-sub-tlv" {
    when "/rt:routing/rt:control-plane-protocols/"+
         "rt:control-plane-protocol/rt:type = 'isis:isis'" {
      description
        "This augment ISIS routing protocol when used";
    }
    description
      "This augments ISIS protocol LSDB TLV22 asla-sub-tlv.";

    uses generic-metric-sub-tlv;
  }

  /* TLV 223 */
  augment "/rt:routing/" +
          "rt:control-plane-protocols/rt:control-plane-protocol"+
          "/isis:isis/isis:database/isis:levels/isis:lsp"+
          "/isis:mt-is-neighbor/isis:neighbor"+
          "/isis:instances/isis:instance" {
    when "/rt:routing/rt:control-plane-protocols/"+
         "rt:control-plane-protocol/rt:type = 'isis:isis'" {
      description
        "This augment ISIS routing protocol when used";
    }
    description
      "This augments ISIS protocol LSDB TLV223.";

    uses generic-metric-sub-tlv;
  }

  augment "/rt:routing/" +
          "rt:control-plane-protocols/rt:control-plane-protocol"+
          "/isis:isis/isis:database/isis:levels/isis:lsp"+
          "/isis:mt-is-neighbor/isis:neighbor"+
          "/isis:instances/isis:instance"+
          "/isis-link-attr:asla-sub-tlvs"+
          "/isis-link-attr:asla-sub-tlv" {
    when "/rt:routing/rt:control-plane-protocols/"+
         "rt:control-plane-protocol/rt:type = 'isis:isis'" {
      description
        "This augment ISIS routing protocol when used";
    }
    description
      "This augments ISIS protocol LSDB TLV223 asla-sub-tlv.";

    uses generic-metric-sub-tlv;
  }

  augment "/rt:routing/rt:control-plane-protocols/"
        + "rt:control-plane-protocol/"
        + "isis:isis/isis:database/isis:levels/isis:lsp/"
        + "isis:router-capabilities/isis-flex-algo:fad-tlvs/"
        + "isis-flex-algo:fad-tlv" {
    when "/rt:routing/rt:control-plane-protocols/"+
         "rt:control-plane-protocol/"+
         "rt:type = 'isis:isis'" {
    description
      "This augment ISIS routing protocol when used";
    }
    description
      "This augments ISIS protocol LSDB router capability.";

    uses faemb-sub-tlv;
    uses faemd-sub-tlv;
    uses fadrb-sub-tlv;
    uses fadbt-sub-tlv;
  }
}
