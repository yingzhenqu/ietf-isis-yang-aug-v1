module iana-igp-algo-types {
  yang-version 1.1;
  namespace "urn:ietf:params:xml:ns:yang:iana-igp-algo-types";
  prefix iana-algo-types;

  organization
    "Internet Assigned Numbers Authority (IANA)";

  contact
    "Internet Assigned Numbers Authority

     ICANN
     12025 Waterfront Drive, Suite 300
     Los Angeles, CA 90094-2536
     United States of America
     
     Tel:    +1 310 301 5800
      &lt;mailto:iana@iana.org&gt;";

  description
    "The YANG module defines the identities for Interior Gateway
     Protocol (IGP) Algorithm Types.

     This YANG module is maintained by IANA and reflects the 'IGP
     Algorithm Types' registry.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This initial version of this YANG module is part of RFC XXXX
     (https://www.rfc-editor.org/info/rfcXXXX); see the RFC itself
     for full legal notices.

     //RFC Ed.: replace XXXX with actual RFC number and remove
       this note

     //RFC Ed.: replace IANA_FOO_URL and remove this note.

     The latest version of this YANG module is available at
     &lt;mailto:iana@iana.org&gt;";

  revision 2025-06-13 {
    description
      "Initial Version";
    reference
      "RFC XXXX: YANG Data Model for OSPF Flexible Algorithm";
  }

  identity algo-type {
    description
      "Base identity for IGP Algorithm Type. The algorithm types
       are defined in IANA IGP Algorithm Types registry.";
  }

  identity algo-spf {
    base algo-type;
    description
      "Shortest Path First (SPF) algorithm based on link metric.";
  }

  identity algo-strict-spf {
    base algo-type;
    description
      "Strict Shortest Path First (SPF) algorithm based on link metric.";
  }
}
